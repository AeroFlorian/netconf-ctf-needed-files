module module-containing-flag {
    yang-version 1.1;
    namespace "urn:module-flag:1.0";
  prefix "module-flag";

  contact
    "florian.salaun@nokia.com";

  description
    "Basic model used for a CTF aiming at make people familiar with NETCONF";

  revision "2024-07-11" {
   description "Creation";
  }

  rpc give-me-the-flag {
    input {
    }
    output {
      leaf flag {
        type string;
        description "The flag";
      }
    }
  }
}
