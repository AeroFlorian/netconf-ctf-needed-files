module module-containing-flag {
    yang-version 1.1;
    namespace "urn:module-flag:1.0";
  prefix "module-flag";

  contact
    "florian.salaun@nokia.com";

  description
    "Basic model used for a CTF aiming at make people familiar with NETCONF";

  revision "2024-07-11" {
   description "Creation";
  }

  notification here-is-the-flag-take-it {
      leaf flag {
        type string;
        description "The flag";
      }
      description "Notification sent periodically containing the flag";
  }
}
