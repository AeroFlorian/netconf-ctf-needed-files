module module-containing-flag {
    yang-version 1.1;
    namespace "urn:module-flag:1.0";
  prefix "module-flag";

  contact
    "florian.salaun@nokia.com";

  description
    "Basic model used for a CTF aiming at make people familiar with NETCONF";

  revision "2024-07-11" {
   description "Creation";
  }

  container flag-container
  {
    list objects-to-modify
    {
        key "name";
        description "List of objects, set 2 objects to get the flag";
        leaf name
        {
            type string;
            description "The name of the object";
        }

        leaf set-me-to-get-the-flag
        {
            type boolean;
            description "Set me to true to get the flag";
        }
    }

      leaf flag
      {
          config false;
          type string;
          description "The flag";
      }
  }
}
