module module-containing-flag {
    yang-version 1.1;
    namespace "urn:module-flag:1.0";
  prefix "module-flag";

  contact
    "florian.salaun@nokia.com";

  description
    "Basic model used for a CTF aiming at make people familiar with NETCONF";

  revision "2024-07-11" {
   description "Creation";
  }

  container flag-container
  {

    list objects-already-created
    {
        key "name";
        description "List of objects that are already present";
        leaf name
        {
            type string;
            description "The name of the object";
        }
    }

    list objects-to-create
    {
        key "name";
        description "List of objects, set one to get the flag";
        leaf name
        {
            type string;
            description "The name of the object";
        }

        leaf points-to
        {
            type leafref {
                path "/flag-container/objects-already-created/name";
            }
            description "Points to another object";
            mandatory true;
        }

        leaf set-me-to-get-the-flag
        {
            type boolean;
            description "Set me to true to get the flag";
        }
    }

      leaf flag
      {
          config false;
          type string;
          description "The flag";
      }
  }
}
